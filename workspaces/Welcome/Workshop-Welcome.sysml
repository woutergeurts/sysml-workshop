package 'Workshop Welcome' {
	doc /* This package owns 
	     * a comment on 
	     * package level
	     */
	
	part def Workshop {
		doc WSDoc1 /* goal: accellerate your development */

	}
	
	part sysmlWorkshop : Workshop {
		doc  /* This workshop will be launched in October */
		
	}
}
