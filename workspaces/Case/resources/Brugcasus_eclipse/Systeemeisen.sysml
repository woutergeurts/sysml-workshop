package Systeemeisen {
    
    requirement <'eis0001'> 'Communicatie met weggebruikers' {
        /* Communicatie met weggebruikers dient plaats te vinden door het geven van 
        lichtsignalen door middel van verkeerslichten */
    }
    
    requirement <'eis0002'> 'Communicatie met scheepvaartverkeer' {
        /* Communicatie met weggebruikers dient plaats te vinden door het geven van 
        lichtsignalen door middel van scheepvaartseinen */
    }
}
