package 'Missiesystemen'{
    
    part def t_brug {
        part de_val: t_Val;
        part de_vaarweg: t_Vaarweg;
        part t_sein_links: t_Scheepvaartsein;
        part t_sein_rechts: t_Scheepvaartsein;
        part bruglicht_onder: t_Bruglicht;
        part bruglicht_boven: t_Bruglicht;
        part plc: t_Besturing;
    }
    
    part def t_Val {
    }
    
    part def t_Vaarweg {
    }
    
    part def t_Bruglicht {
    }
    
    part def t_Scheepvaartsein {
    }
    
    part def t_Besturing {
    }
}
