package Functieboom {
    action 'Kruisen Verkeersstromen'{
        action 'Passeren Scheepvaartverkeer'{
            action 'Stoppen Scheepvaartverkeer';
            action 'Doorlaten Scheepvaartverkeer';
        }
        action 'Passeren Wegverkeer'{
            action 'Stoppen landverkeer';
            action 'Doorlaten Landverkeer';
        }
    }
}
